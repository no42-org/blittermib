CI-SMOKE-MIB DEFINITIONS ::= BEGIN

IMPORTS
    MODULE-IDENTITY, OBJECT-IDENTITY, enterprises
        FROM SNMPv2-SMI;

ciSmokeRoot MODULE-IDENTITY
    LAST-UPDATED "202606060000Z"
    ORGANIZATION "blittermib CI"
    CONTACT-INFO "ci@example.invalid"
    DESCRIPTION  "Smoke MIB for the chart import-drop assertion."
    ::= { enterprises 99998 }

ciSmokeObject OBJECT-IDENTITY
    STATUS  current
    DESCRIPTION "Smoke object."
    ::= { ciSmokeRoot 1 }

END
